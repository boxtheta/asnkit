-- Small application-specific payloads, shared by the example messages.
Payloads DEFINITIONS ::= BEGIN
    id-text OBJECT IDENTIFIER ::= { 1 3 6 1 4 1 99999 1 }
    id-point OBJECT IDENTIFIER ::= { 1 3 6 1 4 1 99999 2 }

    Point ::= SEQUENCE {
        x INTEGER (-100..100),
        y INTEGER (-100..100)
    }
END
